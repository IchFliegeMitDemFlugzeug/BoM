Option Explicit                                                                 ' Требуем явного объявления переменных (меньше “магических” ошибок)

Dim gProjectCodePrefixes                                                         ' Массив префиксов проекта (в нижнем регистре)
Dim gRepeatingSubassembliesInTree                                                ' Флаг: повторять подсборки в дереве (из Settings.txt)
Dim gNonDrawingPartsAsMaterials                                                  ' Флаг: скрывать БЧ-ткань как материалы (из Settings.txt)
Dim gMassOfStandardParts                                                         ' Флаг: показывать массу стандартных изделий (из Settings.txt)
Dim gMassOfPKI                                                                   ' Флаг: показывать массу ПКИ (из Settings.txt)
Dim gMaterialCode                                                                ' Код строки материала из Code.tsv
Dim gCodesDescriptionKeys                                                        ' Массив кодов из Code.tsv, которые ищем в Description
Dim gMetalsKeywords                                                             ' Массив ключей металлов из metals_ru_library.tsv (нижний регистр)
Dim gCompositeKeywords                                                          ' Массив тегов композитов из composites_detect_keywords.tsv (тег + группа)

' -----------------------------                                                    ' Раздел комментария
' Точка входа макроса CATIA                                                        ' Описание
' -----------------------------                                                    ' Раздел комментария
Sub CATMain()                                                                     ' Главная процедура, которую вызывает CATIA

    Dim asmDoc                                                                    ' Переменная для активного документа
    Set asmDoc = CATIA.ActiveDocument                                             ' Берём текущий активный документ CATIA

    If TypeName(asmDoc) <> "ProductDocument" Then                                 ' Если активный документ не сборка (CATProduct)
        MsgBox "Открой активную сборку (CATProduct) и запусти макрос ещё раз.", vbExclamation, "BOM Extract" ' Сообщаем пользователю
        Exit Sub                                                                  ' Выходим из макроса
    End If                                                                        ' Конец проверки типа документа

    Dim rootProd                                                                  ' Переменная для корневого Product
    Set rootProd = asmDoc.Product                                                 ' Получаем корневой продукт сборки

    Dim startLevelText                                                            ' Строка ответа пользователя по стартовому уровню
    startLevelText = InputBox("С какого уровня начать в Excel? Введи: G1..G8 (например G2).", "BOM Extract", "G2") ' Просим уровень

    Dim startLevel                                                                ' Числовой стартовый уровень (1..8)
    startLevel = ParseStartLevel(startLevelText)                                  ' Парсим G1..G8 в число

    If startLevel < 1 Or startLevel > 8 Then                                      ' Если уровень невалиден
        MsgBox "Неверный уровень. Допустимо: G1..G8.", vbExclamation, "BOM Extract" ' Сообщаем
        Exit Sub                                                                  ' Выходим
    End If                                                                        ' Конец проверки уровня

    Dim outXlsx                                                                   ' Путь сохранения Excel
    outXlsx = CATIA.FileSelectionBox("Сохранить спецификацию как Excel", "*.xlsx", 1) ' Диалог “Сохранить как”
    If Trim(outXlsx) = "" Then                                                    ' Если пользователь нажал Cancel
        MsgBox "Сохранение отменено.", vbInformation, "BOM Extract"               ' Сообщаем
        Exit Sub                                                                  ' Выходим
    End If                                                                        ' Конец Cancel
    If LCase(Right(outXlsx, 5)) <> ".xlsx" Then                                   ' Если расширение не .xlsx
        outXlsx = outXlsx & ".xlsx"                                               ' Добавляем расширение
    End If                                                                        ' Конец проверки расширения

    Dim workFolder                                                                ' Папка, где лежат файлы
    workFolder = GetFolderFromFullPath(outXlsx)                                   ' Папка = папка выбранного Excel

    Dim builderPath                                                               ' Путь к ExcelBuilder
    builderPath = workFolder & "\ExcelBuilder.vbs"                                ' ExcelBuilder должен лежать рядом

    If FileExists(builderPath) = False Then                                       ' Если ExcelBuilder не найден
        MsgBox "Не найден ExcelBuilder.vbs в папке:" & vbCrLf & workFolder & vbCrLf & _
               "Положи ExcelBuilder.vbs рядом с тем местом, куда сохраняешь Excel.", vbExclamation, "BOM Extract" ' Подсказка
        Exit Sub                                                                  ' Выходим
    End If                                                                        ' Конец проверки ExcelBuilder

    If LoadSettingsFromFile(workFolder) = False Then                              ' Пробуем прочитать Settings.txt (A1)
        Exit Sub                                                                  ' Если не смогли — выходим
    End If                                                                        ' Конец проверки загрузки настроек

    If LoadCodesFromFile(workFolder) = False Then                                 ' Пробуем загрузить Code.tsv для вычисления codeM (A4)
        Exit Sub                                                                  ' Если не смогли — выходим
    End If                                                                        ' Конец проверки загрузки Code.tsv

    If LoadMaterialLibraries(workFolder) = False Then                             ' Загружаем библиотеки материалов (A6)
        Exit Sub                                                                  ' Если не смогли — выходим
    End If                                                                        ' Конец проверки загрузки библиотек материалов

    Dim payloadPath                                                               ' Путь к промежуточному payload
    payloadPath = workFolder & "\BOM_payload.tsv"                                 ' Payload кладём рядом

    Dim lines                                                                     ' Массив строк payload
    lines = Array()                                                               ' Инициализируем пустым массивом

    ' Заголовок TSV (для ExcelBuilder)                                             ' Пояснение
    lines = ArrayAppendValue(lines, _
        "Depth" & vbTab & "Kind" & vbTab & "Label" & vbTab & "PartNumber" & vbTab & "Definition" & vbTab & _
        "ParentPN" & vbTab & "Qty" & vbTab & "CodeM" & vbTab & "TypeN" & vbTab & "MaterialO" & vbTab & _
        "MassEachKg" & vbTab & "MassTotalKg")                                     ' Столбцы payload (строго по порядку)

    Dim rootPN                                                                    ' PartNumber корня
    rootPN = SafeGetPartNumber(rootProd)                                          ' Берём PartNumber корневой сборки

    Dim rootDef                                                                   ' Definition корня
    rootDef = SafeGetDefinition(rootProd)                                         ' Берём Definition (fallback внутри)

    Dim rootDesc                                                                  ' Description корня (для БЧ и кодов по описанию)
    rootDesc = SafeGetDescription(rootProd)                                       ' Безопасно получаем Description

    Dim rootCodeM                                                                 ' Код для корневой сборки по правилам Code.tsv
    rootCodeM = DetermineCodeM("ASM", rootDesc)                                  ' Вычисляем codeM с учётом БЧ и Code.tsv

    Dim rootLineIndex                                                             ' Индекс строки корня в массиве lines
    rootLineIndex = AppendLineReturnIndex(lines, MakeTSVLine(0, "ASM", rootPN, rootPN, rootDef, "", 1, rootCodeM, "", "", 0, 0)) ' Пишем корень (масса позже)

    Dim rootMassEach                                                              ' Масса 1 шт корня
    rootMassEach = ProcessNodeCollect(rootProd, rootPN, 0, lines)                 ' Обходим дерево, заполняем lines, получаем массу корня

    lines(rootLineIndex) = MakeTSVLine(0, "ASM", rootPN, rootPN, rootDef, "", 1, rootCodeM, "", "", rootMassEach, rootMassEach) ' Перезаписываем корень с массой

    If WriteAllTextUnicode(payloadPath, Join(lines, vbCrLf)) = False Then         ' Если не удалось записать файл
        MsgBox "Не удалось записать файл: " & payloadPath, vbExclamation, "BOM Extract" ' Сообщаем
        Exit Sub                                                                  ' Выходим
    End If                                                                        ' Конец проверки записи

    Dim cmd                                                                       ' Команда запуска ExcelBuilder
    cmd = "wscript.exe " & Quote(builderPath) & " " & Quote(payloadPath) & " " & Quote(outXlsx) & " " & CStr(startLevel) ' Передаём payload, xlsx и старт-уровень

    Dim sh                                                                        ' WScript.Shell для запуска
    Set sh = CreateObject("WScript.Shell")                                        ' Создаём shell
    sh.Run cmd, 1, True                                                           ' Запускаем и ждём завершения

    MsgBox "Готово." & vbCrLf & "Excel: " & outXlsx, vbInformation, "BOM Extract" ' Финальное сообщение

End Sub                                                                           ' Конец CATMain


' -----------------------------                                                    ' Раздел комментария
' Рекурсивная обработка узла (сборка)                                              ' Описание
' Возвращает массу 1 шт данного узла                                               ' Описание
' -----------------------------                                                    ' Раздел комментария
Function ProcessNodeCollect(parentProd, parentPN, depth, ByRef lines)             ' Рекурсивный обход

    Dim sumMassEach                                                               ' Масса 1 шт родителя = сумма масс детей
    sumMassEach = 0                                                               ' Начинаем с 0

    Dim dictQty                                                                   ' Словарь количества по позиции
    Set dictQty = CreateObject("Scripting.Dictionary")                            ' key -> qty

    Dim dictFirst                                                                 ' Словарь “первого объекта” для позиции
    Set dictFirst = CreateObject("Scripting.Dictionary")                          ' key -> child object

    Dim dictDocType                                                               ' Словарь типа документа для позиции
    Set dictDocType = CreateObject("Scripting.Dictionary")                        ' key -> "ProductDocument"/"PartDocument"/"Unknown"

    Dim dictMaterialMass                                                          ' Словарь накопленных масс скрытых материалов
    Set dictMaterialMass = CreateObject("Scripting.Dictionary")                   ' key -> Array(оригинальное имя, суммарная масса)

    Dim ordASM, ordSGTE, ordFAST, ordPKI                                          ' Массивы порядка по группам
    ordASM = Array()                                                              ' Подсборки
    ordSGTE = Array()                                                             ' Детали проекта (по префиксам Project_code)
    ordFAST = Array()                                                             ' Крепёж (DIN/ОСТ)
    ordPKI = Array()                                                              ' ПКИ (прочие)

    Dim i                                                                         ' Счётчик детей
    For i = 1 To parentProd.Products.Count                                        ' Перебираем детей

        Dim child                                                                 ' Дочерний продукт (экземпляр)
        Set child = parentProd.Products.Item(i)                                   ' Берём ребёнка

        Dim refDoc                                                                ' Документ референса
        Set refDoc = Nothing                                                      ' Инициализация
        On Error Resume Next                                                      ' Перехват (если не загружено)
        Set refDoc = child.ReferenceProduct.Parent                                ' Пытаемся получить документ
        On Error GoTo 0                                                           ' Снимаем перехват

        Dim docType                                                               ' Тип документа
        docType = "Unknown"                                                       ' По умолчанию Unknown
        If Not (refDoc Is Nothing) Then                                           ' Если документ получен
            docType = TypeName(refDoc)                                            ' Тип документа
        End If                                                                    ' Конец проверки refDoc

        Dim childPN                                                               ' PartNumber ребёнка
        childPN = SafeGetPartNumber(child)                                        ' Берём PartNumber

        Dim key                                                                   ' Ключ агрегирования
        key = ""                                                                  ' Инициализируем ключ пустой строкой
        If docType = "ProductDocument" And gRepeatingSubassembliesInTree = True Then ' Если это подсборка и в настройках включено повторение
            key = childPN & "|" & docType & "|instance|" & CStr(i)             ' Создаём уникальный ключ на каждое вхождение подсборки
        Else                                                                      ' Если подсборки нужно суммировать или это деталь/ПКИ
            key = childPN & "|" & docType                                         ' Агрегируем по PartNumber и типу документа
        End If                                                                    ' Конец ветвления формирования ключа

        If dictQty.Exists(key) Then                                               ' Если позиция уже встречалась
            dictQty(key) = CLng(dictQty(key)) + 1                                 ' Увеличиваем количество
        Else                                                                      ' Если встретили впервые
            dictQty.Add key, 1                                                    ' Запоминаем qty=1
            dictFirst.Add key, child                                              ' Запоминаем объект (для Definition и т.п.)
            dictDocType.Add key, docType                                          ' Запоминаем тип документа

            ' --- Классификация позиции для порядка вывода ---                    ' Пояснение
            If docType = "ProductDocument" Then                                   ' Если это подсборка
                ordASM = ArrayAppendValue(ordASM, key)                            ' Добавляем в список подсборок
            ElseIf docType = "PartDocument" Then                                  ' Если это деталь

                Dim defText                                                       ' Definition детали
                defText = SafeGetDefinition(child)                                ' Берём Definition

                Dim isFast                                                        ' Флаг “крепёж”
                isFast = IsFastener(childPN, defText)                             ' Проверяем DIN/ОСТ/ДИН/OST

                If isFast = True Then                                             ' Если крепёж
                    ordFAST = ArrayAppendValue(ordFAST, key)                      ' В крепёж
                Else                                                              ' Иначе — не крепёж

                Dim flagSgte                                                   ' Флаг “деталь проекта” по Project_code (имя НЕ конфликтует с функцией IsSGTE)
                    flagSgte = IsSGTE(childPN)                                     ' Вызываем функцию IsSGTE и получаем True/False

                    If flagSgte = True Then                                        ' Если это “своя” деталь по префиксам Project_code
                        ordSGTE = ArrayAppendValue(ordSGTE, key)                   ' Добавляем позицию в список “своих” деталей
                    Else                                                           ' Иначе — это ПКИ
                        ordPKI = ArrayAppendValue(ordPKI, key)                     ' Добавляем позицию в список “ПКИ”
                    End If                                                         ' Конец ветвления “свои детали”/ПКИ

                End If                                                             ' Конец ветвления Fastener/обычный

            Else                                                                   ' Неизвестный тип документа
                ordPKI = ArrayAppendValue(ordPKI, key)                             ' Считаем как ПКИ (чтобы не потерять)
            End If                                                                 ' Конец классификации

        End If                                                                     ' Конец Exists
    Next                                                                           ' Следующий ребёнок

    ' ---- Вывод в нужном порядке: 1) подсборки 2) детали проекта 3) крепёж 4) ПКИ ----      ' Пояснение
    sumMassEach = sumMassEach + EmitGroup(ordASM, "ASM", parentProd, parentPN, depth, dictQty, dictFirst, dictDocType, dictMaterialMass, lines)   ' Подсборки
    sumMassEach = sumMassEach + EmitGroup(ordSGTE, "SGTE", parentProd, parentPN, depth, dictQty, dictFirst, dictDocType, dictMaterialMass, lines) ' Детали проекта (по Project_code)
    sumMassEach = sumMassEach + EmitGroup(ordFAST, "FAST", parentProd, parentPN, depth, dictQty, dictFirst, dictDocType, dictMaterialMass, lines) ' Крепёж
    sumMassEach = sumMassEach + EmitGroup(ordPKI, "PKI", parentProd, parentPN, depth, dictQty, dictFirst, dictDocType, dictMaterialMass, lines)   ' ПКИ

    Call EmitMaterialLines(dictMaterialMass, parentPN, depth, lines)               ' После деталей выводим агрегированные MAT-строки

    ProcessNodeCollect = sumMassEach                                               ' Возвращаем массу 1 шт узла

End Function                                                                       ' Конец ProcessNodeCollect


' -----------------------------                                                    ' Раздел комментария
' Вывод одной группы (ASM/Project/FAST/PKI)                                        ' Описание
' Возвращает вклад массы в родительскую сборку (учитывая qty)                      ' Описание
' -----------------------------                                                    ' Раздел комментария
Function EmitGroup(orderKeys, mode, parentProd, parentPN, depth, dictQty, dictFirst, dictDocType, dictMaterialMass, ByRef lines)

    Dim addMass                                                                    ' Суммарная масса, которую добавит эта группа
    addMass = 0                                                                    ' Начинаем с 0

    Dim i                                                                          ' Счётчик по ключам группы
    For i = 0 To ArrayLastIndex(orderKeys)                                         ' Перебираем ключи

        Dim key                                                                    ' Ключ позиции
        key = orderKeys(i)                                                         ' Берём key

        Dim qty                                                                    ' Количество позиции в родителе
        qty = CLng(dictQty(key))                                                   ' Берём qty

        Dim childObj                                                               ' “Первый объект” позиции
        Set childObj = dictFirst(key)                                              ' Получаем объект

        Dim docType                                                                ' Тип документа позиции
        docType = CStr(dictDocType(key))                                           ' Берём тип

        Dim thisPN                                                                 ' PartNumber позиции
        thisPN = SafeGetPartNumber(childObj)                                       ' Берём PartNumber

        Dim thisDef                                                                ' Definition позиции
        thisDef = SafeGetDefinition(childObj)                                      ' Берём Definition

        Dim thisDesc                                                               ' Description позиции (для БЧ и кодов по описанию)
        thisDesc = SafeGetDescription(childObj)                                    ' Берём Description безопасно

        If docType = "ProductDocument" Then                                        ' Если подсборка

            Dim asmCodeM                                                           ' Код подсборки по правилам Code.tsv
            asmCodeM = DetermineCodeM("ASM", thisDesc)                            ' Вычисляем codeM с учётом Description

            Dim asmLineIndex                                                       ' Индекс строки подсборки в payload
            asmLineIndex = AppendLineReturnIndex(lines, MakeTSVLine(depth + 1, "ASM", thisPN, thisPN, thisDef, parentPN, qty, asmCodeM, "", "", 0, 0)) ' Добавляем строку подсборки (массу пересчитаем)

            Dim asmMassEach                                                        ' Масса 1 шт подсборки
            asmMassEach = ProcessNodeCollect(childObj, thisPN, depth + 1, lines)   ' Рекурсивно обрабатываем подсборку

            lines(asmLineIndex) = MakeTSVLine(depth + 1, "ASM", thisPN, thisPN, thisDef, parentPN, qty, asmCodeM, "", "", asmMassEach, asmMassEach * qty) ' Перезаписываем строку с массой

            addMass = addMass + (asmMassEach * qty)                                ' Добавляем вклад в массу родителя

        ElseIf docType = "PartDocument" Then                                       ' Если деталь

            Dim partDoc                                                            ' Документ детали
            Set partDoc = childObj.ReferenceProduct.Parent                         ' Получаем PartDocument

            Dim partMat                                                            ' Материал детали
            Dim partMassEach                                                       ' Масса 1 шт детали
            Call MeasurePartMaterialAndMass(partDoc, partMat, partMassEach)        ' Измеряем материал и массу

            Dim descHasBCH                                                        ' Флаг наличия БЧ в Description
            descHasBCH = (InStr(LCase(Trim(CStr(thisDesc))), "бч") > 0)           ' Ищем подстроку "бч" без регистра

            Dim isFabric                                                          ' Флаг: материал является тканью/армированием
            isFabric = IsFabricOrCarbonByMaterial(partMat)                         ' Проверяем материал по словарю композитов

            Dim hideAsMaterial                                                    ' Флаг скрытия детали как материала
            hideAsMaterial = (gNonDrawingPartsAsMaterials = True And descHasBCH = True And isFabric = True) ' Выполняем все условия из варианта B

            If hideAsMaterial = True Then                                         ' Если нужно скрыть деталь и собрать массу в материал

                Call AccumulateMaterialMass(dictMaterialMass, partMat, partMassEach * qty) ' Накопление массы материала внутри подсборки
                addMass = addMass + (partMassEach * qty)                          ' Масса учитывается в подсборке

            ElseIf mode = "FAST" Then                                             ' Если крепёж

                Dim fastMassEach                                                  ' Отображаемая масса 1 шт крепежа
                Dim fastMassTotal                                                 ' Отображаемая масса всего крепежа
                If gMassOfStandardParts = True Then                               ' Проверяем флаг отображения массы стандарта
                    fastMassEach = partMassEach                                   ' Показываем массу 1 шт
                    fastMassTotal = partMassEach * qty                            ' Показываем общую массу
                Else                                                              ' Если показывать нельзя
                    fastMassEach = Empty                                          ' Оставляем поле пустым
                    fastMassTotal = Empty                                         ' Оставляем поле пустым
                End If                                                            ' Конец ветвления отображения массы крепежа

                AppendLineReturnIndex lines, MakeTSVLine(depth + 1, "FAST", "крепеж", thisPN, thisDef, parentPN, qty, "крепеж", "", "", fastMassEach, fastMassTotal) ' Строка крепежа с условной массой

                addMass = addMass + (partMassEach * qty)                          ' Массу крепежа учитываем в родителе всегда

            ElseIf mode = "PKI" Then                                              ' Если ПКИ

                Dim pkiMassEach                                                   ' Отображаемая масса 1 шт ПКИ
                Dim pkiMassTotal                                                  ' Отображаемая масса всей позиции ПКИ
                If gMassOfPKI = True Then                                         ' Проверяем флаг отображения массы ПКИ
                    pkiMassEach = partMassEach                                    ' Показываем массу 1 шт
                    pkiMassTotal = partMassEach * qty                             ' Показываем общую массу
                Else                                                              ' Если отображение выключено
                    pkiMassEach = Empty                                           ' Поле пустое
                    pkiMassTotal = Empty                                          ' Поле пустое
                End If                                                            ' Конец ветвления отображения массы ПКИ

                AppendLineReturnIndex lines, MakeTSVLine(depth + 1, "PKI", "ПКИ", thisPN, thisDef, parentPN, qty, "ПКИ", "", "", pkiMassEach, pkiMassTotal) ' Строка ПКИ с условной массой

                addMass = addMass + (partMassEach * qty)                          ' Массу ПКИ учитываем в родителе всегда

            Else                                                                 ' Обычная деталь (по префиксам Project_code либо прочее)

                Dim typeN                                                          ' Класс материала для столбца N (Металл/Композит/Неметалл)
                typeN = GuessCompMetalPlusFoam(partMat)                            ' Классифицируем материал по ключевым словам (см. функцию ниже)

                Dim partCodeM                                                      ' Код детали по правилам Code.tsv
                partCodeM = DetermineCodeM("PART", thisDesc)                      ' Вычисляем codeM с учётом Description

                AppendLineReturnIndex lines, MakeTSVLine(depth + 1,"PART",thisPN,thisPN,thisDef,parentPN,qty,partCodeM,typeN,partMat,partMassEach,partMassEach * qty)                                            ' MassTotalKg (столбец Q)

                addMass = addMass + (partMassEach * qty)                           ' Добавляем вклад в массу родителя

            End If                                                                 ' Конец ветвления скрытия/FAST/PKI/PART

        Else                                                                       ' Если тип неизвестный
            AppendLineReturnIndex lines, MakeTSVLine(depth + 1, "UNKNOWN", thisPN, thisPN, thisDef, parentPN, qty, "", "", "", 0, 0) ' Пишем строку “как есть”
        End If                                                                     ' Конец ветвления по типу

    Next                                                                           ' Следующий ключ

    EmitGroup = addMass                                                            ' Возвращаем суммарный вклад массы

End Function                                                                       ' Конец EmitGroup


' -----------------------------                                                    ' Раздел комментария
' Накопление массы материала для MAT-строк                                         ' Описание
' -----------------------------                                                    ' Раздел комментария
Sub AccumulateMaterialMass(ByRef dictMaterialMass, materialName, massToAdd)

    Dim normKey                                                                   ' Нормализованный ключ материала (для слияния записей)
    normKey = LCase(Trim(CStr(materialName)))                                     ' Приводим имя материала к нижнему регистру без пробелов

    If normKey = "" Then                                                          ' Если имя материала пустое
        Exit Sub                                                                  ' Нечего накапливать
    End If                                                                        ' Конец проверки пустого имени

    Dim displayName                                                               ' Имя материала как хотим показывать в Excel
    displayName = Trim(CStr(materialName))                                        ' Обрезаем пробелы по краям

    If dictMaterialMass.Exists(normKey) Then                                      ' Если запись по материалу уже есть

        Dim existingEntry                                                         ' Существующий массив [имя, масса]
        existingEntry = dictMaterialMass(normKey)                                 ' Достаём запись

        Dim newMass                                                               ' Новая суммарная масса
        newMass = CDbl(existingEntry(1)) + CDbl(massToAdd)                        ' Складываем текущую массу и добавляемую

        dictMaterialMass(normKey) = Array(existingEntry(0), newMass)              ' Обновляем запись с той же витриной имени

    Else                                                                          ' Если материала ещё не было

        dictMaterialMass.Add normKey, Array(displayName, CDbl(massToAdd))         ' Добавляем новый материал и его массу

    End If                                                                        ' Конец ветвления наличия записи

End Sub                                                                            ' Конец AccumulateMaterialMass


' -----------------------------                                                    ' Раздел комментария
' Вывод накопленных MAT-строк в payload                                             ' Описание
' -----------------------------                                                    ' Раздел комментария
Sub EmitMaterialLines(dictMaterialMass, parentPN, depth, ByRef lines)

    Dim matCodeM                                                                  ' Код строки материала из Code.tsv
    matCodeM = GetMaterialCode()                                                  ' Берём сохранённый код (обычно "мат")

    Dim k                                                                        ' Итератор по ключам словаря материалов
    For Each k In dictMaterialMass.Keys                                           ' Перебираем все материалы, которые нужно вывести

        Dim entry                                                                ' Текущая запись массива [имя, масса]
        entry = dictMaterialMass(k)                                               ' Получаем запись по ключу

        Dim displayName                                                          ' Имя материала для вывода
        displayName = ""                                                         ' Инициализируем пустой строкой
        If IsArray(entry) Then                                                   ' Проверяем, что запись — массив
            If UBound(entry) >= 0 Then                                           ' Если есть элемент с именем
                displayName = CStr(entry(0))                                     ' Берём имя материала как есть
            End If                                                               ' Конец проверки наличия имени
        End If                                                                   ' Конец проверки на массив

        Dim totalMass                                                            ' Масса материала для данной подсборки
        totalMass = 0                                                            ' Инициализируем массой 0
        If IsArray(entry) Then                                                   ' Проверяем тип записи
            If UBound(entry) >= 1 Then                                           ' Если есть элемент с массой
                totalMass = CDbl(entry(1))                                       ' Берём накопленную массу
            End If                                                               ' Конец проверки наличия массы
        End If                                                                   ' Конец проверки на массив

        AppendLineReturnIndex lines, MakeTSVLine(depth + 1, "материал", displayName, "", displayName, parentPN, 1, matCodeM, "", displayName, totalMass, totalMass) ' Добавляем MAT-строку как дочерний элемент

    Next                                                                         ' Следующий материал из словаря

End Sub                                                                            ' Конец EmitMaterialLines


' -----------------------------                                                    ' Раздел комментария
' Получение кода для материалов из Code.tsv                                        ' Описание
' -----------------------------                                                    ' Раздел комментария
Function GetMaterialCode()

    If Trim(CStr(gMaterialCode)) <> "" Then                                      ' Если код материала загружен и непустой
        GetMaterialCode = gMaterialCode                                           ' Возвращаем код из файла
    Else                                                                          ' Если по каким-то причинам код не задан
        GetMaterialCode = "мат"                                                  ' Используем дефолтное значение
    End If                                                                        ' Конец проверки наличия кода

End Function                                                                       ' Конец GetMaterialCode


' -----------------------------                                                    ' Раздел комментария
' Измерение материала и массы детали (по твёрдым Body)                             ' Описание
' -----------------------------                                                    ' Раздел комментария
Sub MeasurePartMaterialAndMass(partDoc, ByRef partMat, ByRef partMassEach)        ' Возвращает материал и массу

    partDoc.Activate                                                               ' Активируем документ детали (важно для SPAWorkbench)

    Dim oPart                                                                      ' Объект Part
    Set oPart = partDoc.Part                                                       ' Берём Part

    On Error Resume Next                                                           ' Перехват на случай проблем обновления
    oPart.Update                                                                   ' Обновляем модель
    On Error GoTo 0                                                                ' Снимаем перехват

    partMassEach = 0                                                               ' Масса детали = 0 по умолчанию
    partMat = ""                                                                   ' Материал детали пустой по умолчанию

    Dim bestMat                                                                    ' Первый найденный материал (если не сможем точно)
    bestMat = ""                                                                   ' Инициализация

    Dim b                                                                          ' Счётчик Body
    For b = 1 To oPart.Bodies.Count                                                ' Перебираем все Body

        Dim oBody                                                                  ' Текущий Body
        Set oBody = oPart.Bodies.Item(b)                                           ' Берём Body

        Dim meas                                                                   ' Результат измерения
        meas = MeasureBodyMass(oPart, partDoc, oBody)                              ' Пробуем измерить массу твёрдого Body

        If IsEmpty(meas) Then                                                      ' Если не твёрдое тело
            ' Пропускаем                                                          ' Пояснение
        Else
            partMassEach = partMassEach + CDbl(meas)                               ' Суммируем массу по твёрдым телам

            Dim mi                                                                 ' Материал как Array(name, density, source)
            mi = ResolveMaterialAllWays(partDoc, oPart, oBody)                     ' Ищем материал на Body/Part/и т.д.

            If Trim(CStr(mi(0))) <> "" Then                                        ' Если имя материала найдено
                If bestMat = "" Then                                               ' Если ещё не запоминали материал
                    bestMat = CStr(mi(0))                                          ' Запоминаем первый найденный
                End If                                                             ' Конец bestMat пустой?
            End If                                                                 ' Конец "материал найден?"
        End If                                                                     ' Конец "твёрдое тело?"

    Next                                                                           ' Следующий Body

    ' Итоговый материал детали:                                                    ' Пояснение
    ' 1) если на уровне Part/продукта есть материал — берём его, иначе первый найденный по Body
    Dim miPart                                                                     ' Материал на уровне Part/Product
    miPart = ResolveMaterialAllWays(partDoc, oPart, Nothing)                       ' Ищем материал без Body

    If Trim(CStr(miPart(0))) <> "" Then                                            ' Если нашли на уровне Part/Product
        partMat = CStr(miPart(0))                                                  ' Берём его
    Else                                                                           ' Если на уровне Part/Product нет
        partMat = bestMat                                                          ' Используем первый найденный по Body
    End If                                                                         ' Конец выбора итогового материала

End Sub                                                                            ' Конец MeasurePartMaterialAndMass


' -----------------------------                                                    ' Раздел комментария
' Измерение массы Body (если твёрдое тело)                                         ' Описание
' Возвращает массу (кг) или Empty                                                  ' Описание
' -----------------------------                                                    ' Раздел комментария
Function MeasureBodyMass(oPart, partDoc, oBody)

    Dim spa                                                                         ' SPAWorkbench
    Set spa = partDoc.GetWorkbench("SPAWorkbench")                                 ' Получаем верстак измерений

    Dim inertia                                                                     ' Inertia объект
    Set inertia = Nothing                                                           ' Инициализация

    On Error Resume Next                                                            ' Перехват
    Set inertia = spa.Inertias.Add(oBody)                                           ' Создаём инерцию по Body
    On Error GoTo 0                                                                 ' Снимаем перехват

    If inertia Is Nothing Then                                                      ' Если инерцию создать не удалось
        MeasureBodyMass = Empty                                                     ' Считаем, что измерение невозможно
        Exit Function                                                               ' Выходим
    End If                                                                          ' Конец проверки inertia

    Dim m                                                                           ' Масса
    m = 0                                                                           ' По умолчанию 0
    On Error Resume Next                                                            ' Перехват
    m = inertia.Mass                                                                ' Берём массу (кг)
    On Error GoTo 0                                                                 ' Снимаем

    ' Фильтр “твёрдого тела”: если масса <= 0 — считаем, что это не solid           ' Пояснение
    If CDbl(m) <= 0 Then                                                            ' Если масса не определилась
        MeasureBodyMass = Empty                                                     ' Возвращаем Empty
        Exit Function                                                               ' Выходим
    End If                                                                          ' Конец фильтра массы

    MeasureBodyMass = CDbl(m)                                                       ' Возвращаем массу

End Function                                                                        ' Конец MeasureBodyMass


' -----------------------------                                                    ' Раздел комментария
' Материал: ищем максимально широко                                                 ' Описание
' -----------------------------                                                    ' Раздел комментария
Function ResolveMaterialAllWays(partDoc, oPart, oBody)

    Dim mgr                                                                         ' Менеджер материалов
    Set mgr = GetMaterialManager(partDoc)                                           ' Получаем CATMatManagerVBExt

    Dim mat                                                                         ' Объект материала
    Set mat = Nothing                                                               ' Инициализация

    ' 1) Material на Body                                                           ' Пояснение
    If Not (oBody Is Nothing) Then                                                  ' Если Body передан
        If Not (mgr Is Nothing) Then                                                ' Если менеджер доступен
            On Error Resume Next                                                    ' Перехват
            mgr.GetMaterialOnBody oBody, mat                                        ' Пытаемся получить материал
            On Error GoTo 0                                                         ' Снимаем
            If Not (mat Is Nothing) Then                                            ' Если нашли
                ResolveMaterialAllWays = Array(mat.Name, 0, "Body")                 ' Возвращаем имя
                Exit Function                                                       ' Выходим
            End If                                                                  ' Конец проверки mat
        End If                                                                      ' Конец проверки mgr
    End If                                                                          ' Конец проверки oBody

    ' 2) Material на MainBody                                                       ' Пояснение
    If Not (mgr Is Nothing) Then                                                    ' Если менеджер доступен
        Dim mainB                                                                   ' MainBody
        Set mainB = Nothing                                                         ' Инициализация
        On Error Resume Next                                                         ' Перехват
        Set mainB = oPart.MainBody                                                  ' Берём главный Body
        On Error GoTo 0                                                              ' Снимаем перехват
        If Not (mainB Is Nothing) Then                                              ' Если MainBody есть
            Set mat = Nothing                                                       ' Обнуляем mat
            On Error Resume Next                                                    ' Перехват
            mgr.GetMaterialOnBody mainB, mat                                        ' Пытаемся получить материал
            On Error GoTo 0                                                         ' Снимаем
            If Not (mat Is Nothing) Then                                            ' Если нашли
                ResolveMaterialAllWays = Array(mat.Name, 0, "MainBody")             ' Возвращаем имя
                Exit Function                                                       ' Выходим
            End If                                                                  ' Конец проверки mat
        End If                                                                      ' Конец проверки mainB
    End If                                                                          ' Конец проверки mgr

    ' 3) Material на Part (если метод есть)                                         ' Пояснение
    If Not (mgr Is Nothing) Then                                                    ' Если менеджер доступен
        Set mat = Nothing                                                           ' Обнуляем mat
        On Error Resume Next                                                        ' Перехват
        mgr.GetMaterialOnPart oPart, mat                                            ' Пытаемся получить материал
        On Error GoTo 0                                                             ' Снимаем
        If Not (mat Is Nothing) Then                                                ' Если нашли
            ResolveMaterialAllWays = Array(mat.Name, 0, "Part")                     ' Возвращаем имя
            Exit Function                                                           ' Выходим
        End If                                                                      ' Конец проверки mat
    End If                                                                          ' Конец проверки mgr

    ' 4) Material на Product внутри CATPart                                         ' Пояснение
    If Not (mgr Is Nothing) Then                                                    ' Если менеджер доступен
        Set mat = Nothing                                                           ' Обнуляем mat
        On Error Resume Next                                                        ' Перехват
        mgr.GetMaterialOnProduct partDoc.Product, mat                               ' Пытаемся получить материал
        On Error GoTo 0                                                             ' Снимаем
        If Not (mat Is Nothing) Then                                                ' Если нашли
            ResolveMaterialAllWays = Array(mat.Name, 0, "Product")                  ' Возвращаем имя
            Exit Function                                                           ' Выходим
        End If                                                                      ' Конец проверки mat
    End If                                                                          ' Конец проверки mgr

    ' 5) Параметр Material/Материал                                                 ' Пояснение
    Dim pm                                                                          ' Переменная для параметра
    Set pm = TryFindMaterialParameter(partDoc)                                      ' Пытаемся найти параметр материала
    If Not (pm Is Nothing) Then                                                     ' Если параметр найден
        Dim valStr                                                                  ' Строковое значение параметра
        valStr = ""                                                                ' Инициализация
        On Error Resume Next                                                        ' Перехват
        valStr = pm.ValueAsString                                                   ' Читаем как строку
        On Error GoTo 0                                                             ' Снимаем перехват
        ResolveMaterialAllWays = Array(valStr, 0, "Parameter")                      ' Возвращаем значение
        Exit Function                                                               ' Выходим
    End If                                                                          ' Конец проверки параметра

    ResolveMaterialAllWays = Array("", 0, "NotFound")                               ' Если нигде не нашли — возвращаем пусто

End Function                                                                        ' Конец ResolveMaterialAllWays


Function GetMaterialManager(partDoc)

    Dim mgr                                                                         ' Переменная для менеджера материалов
    Set mgr = Nothing                                                               ' Инициализация

    On Error Resume Next                                                            ' Перехват ошибок
    Set mgr = partDoc.Part.GetItem("CATMatManagerVBExt")                            ' Пытаемся получить менеджер из Part
    If Err.Number <> 0 Or mgr Is Nothing Then                                       ' Если не получилось
        Err.Clear                                                                  ' Сбрасываем ошибку
        Set mgr = partDoc.Product.GetItem("CATMatManagerVBExt")                     ' Пытаемся получить менеджер из Product
    End If                                                                          ' Конец фолбэка
    On Error GoTo 0                                                                 ' Снимаем перехват

    Set GetMaterialManager = mgr                                                    ' Возвращаем менеджер (или Nothing)

End Function                                                                        ' Конец GetMaterialManager


Function TryFindMaterialParameter(partDoc)

    Dim params                                                                      ' Коллекция параметров Part
    Set params = partDoc.Part.Parameters                                            ' Берём параметры

    Dim names                                                                       ' Массив возможных имён параметра материала
    names = Array("Material", "MATERIAL", "Материал", "МАТЕРИАЛ", "Mat", "MAT")     ' Перечень вариантов имён

    Dim i                                                                           ' Счётчик
    For i = 0 To UBound(names)                                                      ' Перебираем варианты имён
        Dim p                                                                       ' Параметр
        Set p = Nothing                                                             ' Инициализация
        On Error Resume Next                                                        ' Перехват
        Set p = params.Item(names(i))                                               ' Пытаемся получить параметр по имени
        On Error GoTo 0                                                             ' Снимаем перехват
        If Not (p Is Nothing) Then                                                  ' Если нашли
            Set TryFindMaterialParameter = p                                        ' Возвращаем найденный параметр
            Exit Function                                                           ' Выходим
        End If                                                                      ' Конец проверки p
    Next                                                                            ' Следующий вариант имени

    Set TryFindMaterialParameter = Nothing                                          ' Если не нашли — возвращаем Nothing

End Function                                                                        ' Конец TryFindMaterialParameter


' -----------------------------                                                    ' Раздел комментария
' Definition: берём Definition, иначе Nomenclature/Name                             ' Описание
' -----------------------------                                                    ' Раздел комментария
Function SafeGetDefinition(prodObj)

    Dim s                                                                           ' Строка результата
    s = ""                                                                         ' Инициализация

    On Error Resume Next                                                           ' Перехват
    s = prodObj.ReferenceProduct.Definition                                        ' Пытаемся взять Definition у референса
    If Err.Number <> 0 Or Trim(s) = "" Then                                        ' Если не получилось или пусто
        Err.Clear                                                                  ' Сбрасываем ошибку
        s = prodObj.Definition                                                     ' Пытаемся взять Definition у экземпляра
    End If                                                                         ' Конец фолбэка
    On Error GoTo 0                                                                ' Снимаем перехват

    If Trim(s) = "" Then                                                           ' Если всё ещё пусто
        s = SafeGetNomenclature(prodObj)                                            ' Фолбэк на Nomenclature/Name
    End If                                                                         ' Конец проверки пустоты

    SafeGetDefinition = s                                                          ' Возвращаем итог

End Function                                                                        ' Конец SafeGetDefinition


Function SafeGetDescription(prodObj)

    Dim s                                                                           ' Строка результата
    s = ""                                                                         ' Инициализируем пустой строкой

    On Error Resume Next                                                           ' Перехват ошибок чтения Description
    s = prodObj.Description                                                        ' 1-я попытка: Description экземпляра (DescriptionInst)
    If Err.Number <> 0 Or Trim(s) = "" Then                                        ' Если получить не удалось или строка пустая
        Err.Clear                                                                  ' Чистим ошибку для повторной попытки
        s = prodObj.ReferenceProduct.Description                                   ' 2-я попытка: Description референса (DescriptionRef)
    End If                                                                         ' Конец проверки первой попытки
    On Error GoTo 0                                                                ' Снимаем перехват ошибок

    SafeGetDescription = CStr(s)                                                   ' Возвращаем строку Description (может быть пустой)

End Function                                                                        ' Конец SafeGetDescription


Function SafeGetPartNumber(prodObj)

    Dim s                                                                           ' Строка результата
    s = ""                                                                         ' Инициализация
    On Error Resume Next                                                           ' Перехват
    s = prodObj.ReferenceProduct.PartNumber                                         ' Пытаемся взять PartNumber у референса
    If Err.Number <> 0 Or Trim(s) = "" Then                                        ' Если не получилось или пусто
        Err.Clear                                                                  ' Сбрасываем
        s = prodObj.PartNumber                                                     ' Пытаемся взять PartNumber у экземпляра
    End If                                                                         ' Конец фолбэка
    On Error GoTo 0                                                                ' Снимаем перехват
    SafeGetPartNumber = s                                                          ' Возвращаем

End Function                                                                        ' Конец SafeGetPartNumber


Function SafeGetNomenclature(prodObj)

    Dim s                                                                           ' Строка результата
    s = ""                                                                         ' Инициализация
    On Error Resume Next                                                           ' Перехват
    s = prodObj.ReferenceProduct.Nomenclature                                      ' Пытаемся взять Nomenclature у референса
    If Err.Number <> 0 Or Trim(s) = "" Then                                        ' Если не получилось/пусто
        Err.Clear                                                                  ' Сбрасываем
        s = prodObj.ReferenceProduct.Name                                          ' Фолбэк на Name референса
    End If                                                                         ' Конец фолбэка
    If Err.Number <> 0 Or Trim(s) = "" Then                                        ' Если всё ещё не получилось
        Err.Clear                                                                  ' Сбрасываем
        s = prodObj.Name                                                           ' Фолбэк на Name экземпляра
    End If                                                                         ' Конец второго фолбэка
    On Error GoTo 0                                                                ' Снимаем перехват
    SafeGetNomenclature = s                                                        ' Возвращаем

End Function                                                                        ' Конец SafeGetNomenclature


' -----------------------------                                                    ' Раздел комментария
' Классификация                                                                     ' Описание
' -----------------------------                                                    ' Раздел комментария
Function IsSGTE(partNumber)

    Dim normalizedPN                                                               ' PartNumber, приведённый к нижнему регистру и без пробелов
    normalizedPN = LCase(Trim(CStr(partNumber)))                                   ' Чистим исходный PartNumber

    Dim ubPrefixes                                                                 ' Индекс последнего префикса из настроек
    ubPrefixes = ArrayLastIndex(gProjectCodePrefixes)                              ' Проверяем, есть ли что-нибудь в списке Project_code

    If ubPrefixes = -1 Then                                                        ' Если список пуст
        IsSGTE = False                                                             ' Нечего сопоставлять — считаем позицию “чужой”
        Exit Function                                                              ' Выходим раньше
    End If                                                                         ' Конец проверки пустого списка

    Dim i                                                                          ' Счётчик по префиксам
    For i = 0 To ubPrefixes                                                        ' Перебираем все заданные префиксы

        Dim prefix                                                                 ' Текущий префикс
        prefix = LCase(Trim(CStr(gProjectCodePrefixes(i))))                        ' Нормализуем префикс из настроек

        If prefix <> "" Then                                                      ' Пустые значения пропускаем
            If InStr(normalizedPN, prefix) > 0 Then                                ' Ищем префикс в любой позиции PartNumber без регистра
                IsSGTE = True                                                      ' Это “своя” деталь/сборка
                Exit Function                                                      ' Сразу выходим — хватило одного совпадения
            End If                                                                 ' Конец проверки совпадения
        End If                                                                     ' Конец проверки пустого префикса

    Next                                                                           ' Следующий префикс

    IsSGTE = False                                                                 ' Если дошли сюда — совпадений не было

End Function                                                                        ' Конец IsSGTE


Function DetermineCodeM(kindText, descriptionText)

    Dim descNorm                                                                   ' Description в нижнем регистре и без пробелов по краям
    descNorm = LCase(Trim(CStr(descriptionText)))                                  ' Нормализуем входной Description

    If InStr(descNorm, "бч") > 0 Then                                              ' Самый высокий приоритет: если нашли "бч" в Description
        DetermineCodeM = "бч"                                                     ' Возвращаем код бч
        Exit Function                                                              ' Выходим сразу
    End If                                                                         ' Конец проверки БЧ

    Dim i                                                                          ' Счётчик по кодам, которые ищем в Description
    For i = 0 To ArrayLastIndex(gCodesDescriptionKeys)                             ' Перебираем все коды из Code.tsv с пометкой description

        Dim keyText                                                                ' Текущий код для поиска
        keyText = LCase(Trim(CStr(gCodesDescriptionKeys(i))))                      ' Нормализуем код из файла

        If keyText <> "" Then                                                     ' Пустые значения пропускаем
            If InStr(descNorm, keyText) > 0 Then                                   ' Если код встретился подстрокой в Description
                DetermineCodeM = gCodesDescriptionKeys(i)                          ' Возвращаем исходный код (в том регистре, как в файле)
                Exit Function                                                      ' Выходим
            End If                                                                 ' Конец проверки вхождения
        End If                                                                     ' Конец проверки пустого кода

    Next                                                                           ' Следующий код из списка

    If kindText = "ASM" Then                                                     ' Дефолт для сборок и подсборок
        DetermineCodeM = "сб"                                                     ' Код сборки
    ElseIf kindText = "PART" Then                                                ' Дефолт для деталей
        DetermineCodeM = "д"                                                      ' Код детали
    Else                                                                           ' Остальные категории оставляем как есть
        DetermineCodeM = ""                                                       ' Пустой код (не трогаем существующую логику)
    End If                                                                         ' Конец выбора по типу

End Function                                                                        ' Конец DetermineCodeM


Function IsFastener(partNumber, defText)

    Dim s                                                                           ' Строка для поиска
    s = LCase(CStr(partNumber) & " " & CStr(defText))                              ' Склеиваем и приводим к нижнему регистру

    If InStr(s, "din") > 0 Then                                                    ' Англ. DIN
        IsFastener = True                                                          ' Это крепёж
    ElseIf InStr(s, "ост") > 0 Then                                                ' Рус. ОСТ
        IsFastener = True                                                          ' Это крепёж
    ElseIf InStr(s, "ost") > 0 Then                                                ' Англ. OST
        IsFastener = True                                                          ' Это крепёж
    ElseIf InStr(s, "дин") > 0 Then                                                ' Рус. ДИН
        IsFastener = True                                                          ' Это крепёж
    Else                                                                           ' Иначе
        IsFastener = False                                                         ' Не крепёж
    End If                                                                         ' Конец ветвления

End Function                                                                        ' Конец IsFastener


Function IsFabricOrCarbonByMaterial(materialName)

    Dim materialText                                                               ' Материал в исходном виде
    materialText = CStr(materialName)                                              ' Превращаем материал в строку, оставляя пробелы

    Dim materialLower                                                              ' Материал в нижнем регистре для поиска без регистра
    materialLower = LCase(materialText)                                            ' Приводим к нижнему регистру, пробелы сохраняются

    If Trim(materialLower) = "" Then                                              ' Если материала нет (только пробелы)
        IsFabricOrCarbonByMaterial = False                                         ' Считаем, что это не ткань
        Exit Function                                                              ' Выходим
    End If                                                                         ' Конец проверки пустого текста

    IsFabricOrCarbonByMaterial = MatchesCompositeKeywords(materialLower, True)     ' Ищем признаки ткани/армирования по словарю

End Function                                                                        ' Конец IsFabricOrCarbonByMaterial


' -----------------------------                                                    ' Раздел комментария
' Класс материала для столбца N                                                     ' Описание
' Возвращает: "Металл" / "Композит" / "Неметалл" / ""                               ' Описание
' -----------------------------                                                    ' Раздел комментария
Function GuessCompMetalPlusFoam(materialName)

    Dim materialText                                                               ' Материал как строка из CATIA
    materialText = CStr(materialName)                                              ' Сохраняем исходные пробелы и порядок символов

    Dim materialLower                                                              ' Материал в нижнем регистре для поиска
    materialLower = LCase(materialText)                                            ' Переводим в нижний регистр без удаления пробелов

    If Trim(materialLower) = "" Then                                              ' Если материал не задан/не найден
        GuessCompMetalPlusFoam = ""                                               ' Возвращаем пусто (чтобы было видно, что материал не определён)
        Exit Function                                                              ' Выходим
    End If                                                                         ' Конец проверки пустого материала

    If MatchesCompositeKeywords(materialLower, False) = True Then                  ' Сначала ищем совпадения по тегам композитов
        GuessCompMetalPlusFoam = "Композит"                                        ' Возвращаем класс "Композит"
        Exit Function                                                              ' Выходим сразу после обнаружения композита
    End If                                                                         ' Конец проверки композита

    If IsMetalByLibrary(materialLower) = True Then                                 ' Если нет композита — проверяем металл
        GuessCompMetalPlusFoam = "Металл"                                          ' Возвращаем класс "Металл"
        Exit Function                                                              ' Выходим после определения металла
    End If                                                                         ' Конец проверки металла

    GuessCompMetalPlusFoam = "Неметалл"                                            ' Если не найдено ни металла, ни композита — считаем неметаллом

End Function                                                                        ' Конец GuessCompMetalPlusFoam


Function MatchesCompositeKeywords(materialLower, onlyFabricGroups)

    Dim i                                                                          ' Счётчик по ключевым словам композитов
    For i = 0 To ArrayLastIndex(gCompositeKeywords)                                ' Перебираем все записи словаря

        Dim entry                                                                  ' Текущая запись (массив тег/группа)
        entry = gCompositeKeywords(i)                                              ' Берём запись по индексу

        If IsArray(entry) Then                                                     ' Проверяем, что запись действительно массив

            Dim tagText                                                           ' Ключевой фрагмент
            tagText = ""                                                         ' Инициализируем пустой строкой
            If UBound(entry) >= 0 Then                                             ' Проверяем наличие элемента тега
                tagText = CStr(entry(0))                                           ' Берём тег из записи (уже в нижнем регистре)
            End If                                                                 ' Конец проверки наличия тега

            Dim groupText                                                         ' Название группы (армирование/смолы и т.п.)
            groupText = ""                                                       ' Инициализируем пустой строкой
            If UBound(entry) >= 1 Then                                             ' Проверяем наличие группы
                groupText = CStr(entry(1))                                         ' Берём группу из записи (уже в нижнем регистре)
            End If                                                                 ' Конец проверки наличия группы

            If Trim(tagText) <> "" Then                                          ' Убеждаемся, что тег заполнен

                If onlyFabricGroups = False Or IsFabricGroupName(groupText) = True Then ' Фильтруем по группам, если нужно искать только ткани

                    If InStr(materialLower, tagText) > 0 Then                      ' Ищем точное вхождение тега в материале без учёта регистра
                        MatchesCompositeKeywords = True                             ' Нашли соответствие
                        Exit Function                                              ' Выходим раньше
                    End If                                                         ' Конец проверки совпадения

                End If                                                             ' Конец проверки группы для ткани

            End If                                                                 ' Конец проверки заполненности

        End If                                                                    ' Конец проверки записи на массив

    Next                                                                           ' Следующая запись в словаре

    MatchesCompositeKeywords = False                                               ' Если дошли сюда — совпадений нет

End Function                                                                        ' Конец MatchesCompositeKeywords


Function IsFabricGroupName(groupName)

    Dim g                                                                          ' Нормализованное имя группы
    g = LCase(Trim(CStr(groupName)))                                               ' Приводим к нижнему регистру

    If g = "армирование" Then                                                    ' Группа армирования (ткани/волокна)
        IsFabricGroupName = True                                                   ' Считаем тканью
        Exit Function                                                              ' Выходим
    End If                                                                         ' Конец проверки армирования

    If g = "полуфабрикаты/структура" Then                                        ' Препреги/структура переплетения
        IsFabricGroupName = True                                                   ' Считаем тканью
        Exit Function                                                              ' Выходим
    End If                                                                         ' Конец проверки полуфабрикатов

    If g = "размерность/плотность" Then                                          ' Плотность тканей (g/m2 и т.п.)
        IsFabricGroupName = True                                                   ' Считаем тканью
        Exit Function                                                              ' Выходим
    End If                                                                         ' Конец проверки плотности

    If g = "бренды/коммерческие обозначения" Then                                ' Бренды тканей/волокон
        IsFabricGroupName = True                                                   ' Считаем тканью
        Exit Function                                                              ' Выходим
    End If                                                                         ' Конец проверки брендов

    IsFabricGroupName = False                                                      ' Остальные группы не считаем тканями

End Function                                                                        ' Конец IsFabricGroupName


Function KeywordMatchesText(tagText, modeText, materialText, groupText)

    Dim mode                                                                       ' Нормализованный режим поиска
    mode = LCase(Trim(CStr(modeText)))                                             ' Приводим режим к нижнему регистру

    Dim tag                                                                        ' Нормализованный тег
    tag = LCase(Trim(CStr(tagText)))                                               ' Приводим тег к нижнему регистру

    Dim mat                                                                        ' Материал в нижнем регистре
    mat = LCase(Trim(CStr(materialText)))                                          ' Нормализуем материал

    If mode = "contains" Then                                                    ' Если нужно искать подстроку
        KeywordMatchesText = (InStr(mat, tag) > 0)                                 ' Проверяем вхождение тега в материал
        Exit Function                                                              ' Выходим после проверки contains
    End If                                                                         ' Конец ветки contains

    If mode = "regex" Then                                                       ' Если нужно искать по регулярному выражению

        Dim needLaritCheck                                                         ' Флаг осторожной проверки Larit 285/287
        needLaritCheck = (tag = "285" Or tag = "287")                           ' Определяем, относится ли тег к осторожным

        If needLaritCheck = True Then                                              ' Для тегов 285/287 нужна доп. проверка контекста
            If InStr(mat, "larit") = 0 And InStr(mat, "l285") = 0 And InStr(mat, "l 285") = 0 And _
               InStr(mat, "l-285") = 0 And InStr(mat, "l287") = 0 And InStr(mat, "l 287") = 0 And _
               InStr(mat, "l-287") = 0 Then                                      ' Проверяем наличие Larit/L-форм в материале
                KeywordMatchesText = False                                         ' Без контекста Larit не считаем совпадением
                Exit Function                                                      ' Выходим раньше
            End If                                                                 ' Конец проверки контекста Larit
        End If                                                                     ' Конец ветки осторожной проверки

        Dim re                                                                     ' Объект регулярного выражения
        Set re = CreateObject("VBScript.RegExp")                                  ' Создаём RegExp
        re.Pattern = tag                                                           ' Устанавливаем паттерн
        re.IgnoreCase = True                                                       ' Ищем без регистра
        re.Global = False                                                          ' Достаточно первого совпадения

        KeywordMatchesText = re.Test(mat)                                          ' Тестируем регулярное выражение
        Exit Function                                                              ' Выходим после проверки regex

    End If                                                                         ' Конец ветки regex

    KeywordMatchesText = False                                                     ' Если режим неизвестен — считаем, что совпадения нет

End Function                                                                        ' Конец KeywordMatchesText


Function IsMetalByLibrary(materialLower)

    Dim m                                                                          ' Счётчик по ключам металлов
    For m = 0 To ArrayLastIndex(gMetalsKeywords)                                   ' Перебираем все ключи из библиотеки металлов

        Dim key                                                                   ' Текущий ключ металла
        key = Trim(CStr(gMetalsKeywords(m)))                                      ' Берём ключ и чистим пробелы по краям

        If key <> "" Then                                                        ' Проверяем, что строка не пустая
            If InStr(materialLower, LCase(key)) > 0 Then                          ' Ищем ключ металла в материале без учёта регистра
                IsMetalByLibrary = True                                           ' Нашли металл
                Exit Function                                                     ' Выходим
            End If                                                                ' Конец проверки вхождения
        End If                                                                    ' Конец проверки пустой строки

    Next                                                                           ' Следующий ключ металла

    IsMetalByLibrary = False                                                      ' Если ничего не нашли — это не металл по библиотеке

End Function                                                                        ' Конец IsMetalByLibrary


' -----------------------------                                                    ' Раздел комментария
' Payload TSV                                                                       ' Описание
' -----------------------------                                                    ' Раздел комментария
Function MakeTSVLine(depth, kind, label, partNumber, defText, parentPN, qty, codeM, typeN, materialO, massEach, massTotal)

    MakeTSVLine = _
        CStr(depth) & vbTab & _
        CleanTSV(kind) & vbTab & _
        CleanTSV(label) & vbTab & _
        CleanTSV(partNumber) & vbTab & _
        CleanTSV(defText) & vbTab & _
        CleanTSV(parentPN) & vbTab & _
        CStr(qty) & vbTab & _
        CleanTSV(codeM) & vbTab & _
        CleanTSV(typeN) & vbTab & _
        CleanTSV(materialO) & vbTab & _
        Replace(CStr(massEach), ",", ".") & vbTab & _
        Replace(CStr(massTotal), ",", ".")

End Function                                                                        ' Конец MakeTSVLine


Function CleanTSV(s)

    Dim t                                                                           ' Рабочая строка
    t = CStr(s)                                                                    ' Приводим к строке
    t = Replace(t, vbTab, " ")                                                     ' Убираем табуляции (ломают TSV)
    t = Replace(t, vbCr, " ")                                                      ' Убираем CR
    t = Replace(t, vbLf, " ")                                                      ' Убираем LF
    CleanTSV = Trim(t)                                                             ' Возвращаем Trim

End Function                                                                        ' Конец CleanTSV


Function AppendLineReturnIndex(ByRef arr, line)

    Dim ub                                                                          ' Индекс последнего элемента
    ub = ArrayLastIndex(arr)                                                        ' Получаем последний индекс

    If ub = -1 Then                                                                ' Если массив пуст
        ReDim arr(0)                                                               ' Создаём массив из 1 элемента
        arr(0) = line                                                              ' Пишем строку
        AppendLineReturnIndex = 0                                                  ' Возвращаем индекс 0
    Else                                                                           ' Если массив не пуст
        ReDim Preserve arr(ub + 1)                                                 ' Увеличиваем массив на 1
        arr(ub + 1) = line                                                         ' Пишем новую строку
        AppendLineReturnIndex = ub + 1                                             ' Возвращаем индекс добавленного элемента
    End If                                                                         ' Конец ветвления

End Function                                                                        ' Конец AppendLineReturnIndex


' -----------------------------                                                    ' Раздел комментария
' Загрузка настроек из Settings.txt                                                 ' Описание
' -----------------------------                                                    ' Раздел комментария
Function LoadSettingsFromFile(workFolder)

    Dim settingsPath                                                               ' Полный путь к Settings.txt
    settingsPath = workFolder & "\Settings.txt"                                   ' Файл настроек лежит рядом с выгрузкой

    If FileExists(settingsPath) = False Then                                       ' Если Settings.txt нет
        MsgBox "Не найден Settings.txt в папке:" & vbCrLf & workFolder & vbCrLf & _
               "Положи Settings.txt рядом со скриптами и попробуй снова.", vbExclamation, "BOM Extract" ' Понятное сообщение и подсказка
        LoadSettingsFromFile = False                                               ' Сообщаем об ошибке загрузки
        Exit Function                                                              ' Выходим из функции
    End If                                                                        ' Конец проверки наличия файла

    gProjectCodePrefixes = Array()                                                 ' Сбрасываем массив префиксов проекта
    gRepeatingSubassembliesInTree = False                                          ' Дефолт: подсборки суммируются
    gNonDrawingPartsAsMaterials = False                                            ' Дефолт: БЧ-ткань показываем как детали
    gMassOfStandardParts = False                                                   ' Дефолт: массы стандарта не отображаем
    gMassOfPKI = False                                                             ' Дефолт: массы ПКИ не отображаем

    Dim readOk                                                                    ' Флаг успешного чтения файла
    readOk = False                                                                ' Инициализируем ложью

    Dim settingsContent                                                           ' Содержимое файла настроек
    settingsContent = ReadAllText(settingsPath, readOk)                           ' Пробуем прочитать файл целиком

    If readOk = False Then                                                        ' Если прочитать не удалось
        MsgBox "Не удалось прочитать Settings.txt:" & vbCrLf & settingsPath, vbExclamation, "BOM Extract" ' Сообщаем пользователю
        LoadSettingsFromFile = False                                               ' Возвращаем ошибку
        Exit Function                                                              ' Выходим
    End If                                                                        ' Конец проверки чтения

    Dim normalizedText                                                            ' Текст с нормализованными переводами строк
    normalizedText = Replace(settingsContent, vbCrLf, vbLf)                       ' Приводим CRLF к LF
    normalizedText = Replace(normalizedText, vbCr, vbLf)                          ' Убираем одиночные CR

    Dim rows                                                                      ' Массив строк файла
    rows = Split(normalizedText, vbLf)                                            ' Делим файл по строкам

    Dim i                                                                         ' Счётчик строк
    For i = 0 To UBound(rows)                                                     ' Перебираем строки настроек

        Dim line                                                                  ' Текущая строка
        line = Trim(CStr(rows(i)))                                                ' Обрезаем пробелы вокруг

        If line = "" Then                                                        ' Пустые строки пропускаем
            ' Пропуск                                                            ' Пояснение
        ElseIf InStr(line, "=") = 0 Then                                         ' Если нет разделителя ключ=значение
            ' Пропуск                                                            ' Пояснение
        Else                                                                      ' Нашли потенциальную пару ключ=значение

            Dim eqPos                                                             ' Позиция символа "="
            eqPos = InStr(line, "=")                                            ' Ищем индекс разделителя

            Dim keyText                                                           ' Имя параметра
            keyText = Trim(Left(line, eqPos - 1))                                 ' Берём часть слева от "=" и чистим

            Dim valueText                                                         ' Текст значения параметра
            valueText = Trim(Mid(line, eqPos + 1))                                ' Берём часть справа и чистим

            Select Case LCase(keyText)                                            ' Определяем параметр по имени
                Case "project_code"                                              ' Список префиксов проекта
                    gProjectCodePrefixes = ParseProjectCodeList(valueText)        ' Парсим список в массив
                Case "repeating_subassemblies_in_tree"                           ' Флаг повторения подсборок
                    gRepeatingSubassembliesInTree = ParseFlexibleBoolean(valueText) ' Конвертируем строку в bool
                Case "non-drawing_parts_as_materials"                            ' Флаг скрытия БЧ-ткань
                    gNonDrawingPartsAsMaterials = ParseFlexibleBoolean(valueText) ' Конвертируем строку в bool
                Case "mass_of_standard_parts"                                    ' Флаг показа массы стандарта
                    gMassOfStandardParts = ParseFlexibleBoolean(valueText)        ' Конвертируем строку в bool
                Case "mass_of_pki"                                               ' Флаг показа массы ПКИ
                    gMassOfPKI = ParseFlexibleBoolean(valueText)                  ' Конвертируем строку в bool
                Case Else                                                         ' Неизвестный параметр
                    ' Пропускаем неизвестные строки                              ' Пояснение
            End Select                                                            ' Конец выбора по имени параметра

        End If                                                                    ' Конец проверки строки

    Next                                                                          ' Переходим к следующей строке

    LoadSettingsFromFile = True                                                   ' Сообщаем об успешной загрузке

End Function                                                                       ' Конец LoadSettingsFromFile


Function LoadCodesFromFile(workFolder)

    Dim codePath                                                                   ' Полный путь к Code.tsv
    codePath = workFolder & "\\Code.tsv"                                           ' Файл кодов лежит рядом с выгрузкой

    If FileExists(codePath) = False Then                                           ' Если Code.tsv нет
        MsgBox "Не найден Code.tsv в папке:" & vbCrLf & workFolder & vbCrLf & _
               "Положи Code.tsv рядом со скриптами и попробуй снова.", vbExclamation, "BOM Extract" ' Сообщаем о необходимости файла
        LoadCodesFromFile = False                                                  ' Сообщаем об ошибке загрузки
        Exit Function                                                              ' Выходим из функции
    End If                                                                         ' Конец проверки наличия файла

    gCodesDescriptionKeys = Array()                                                ' Сбрасываем список кодов, которые ищем в Description
    gMaterialCode = "мат"                                                         ' Дефолтный код материала на случай отсутствия в файле

    Dim readOk                                                                    ' Флаг успешного чтения Code.tsv
    readOk = False                                                                ' Инициализируем ложью

    Dim codesContent                                                              ' Содержимое Code.tsv
    codesContent = ReadAllText(codePath, readOk)                                  ' Пробуем прочитать файл целиком

    If readOk = False Then                                                        ' Если прочитать не удалось
        MsgBox "Не удалось прочитать Code.tsv:" & vbCrLf & codePath, vbExclamation, "BOM Extract" ' Сообщаем пользователю
        LoadCodesFromFile = False                                                  ' Возвращаем ошибку
        Exit Function                                                              ' Выходим
    End If                                                                        ' Конец проверки чтения

    Dim normalizedText                                                            ' Текст с нормализованными переводами строк
    normalizedText = Replace(codesContent, vbCrLf, vbLf)                          ' Приводим CRLF к LF
    normalizedText = Replace(normalizedText, vbCr, vbLf)                          ' Убираем одиночные CR

    Dim rows                                                                      ' Массив строк файла
    rows = Split(normalizedText, vbLf)                                            ' Делим файл по строкам

    Dim i                                                                         ' Счётчик строк
    For i = 0 To UBound(rows)                                                     ' Перебираем строки Code.tsv

        Dim line                                                                  ' Текущая строка
        line = Trim(CStr(rows(i)))                                                ' Обрезаем пробелы вокруг

        If line = "" Then                                                        ' Пустые строки пропускаем
            ' Пропуск                                                             ' Пояснение
        Else                                                                      ' Есть содержимое строки

            Dim cols                                                              ' Колонки, разделённые табами
            cols = Split(line, vbTab)                                             ' Разбиваем строку по табуляции

            Dim codeKey                                                           ' Код из первой колонки
            codeKey = ""                                                         ' Инициализация пустой строкой
            If UBound(cols) >= 0 Then                                             ' Если есть хотя бы одна колонка
                codeKey = Trim(CStr(cols(0)))                                     ' Берём первый столбец
            End If                                                                ' Конец проверки наличия колонок

            Dim hasDescriptionFlag                                               ' Флаг наличия пометки description
            hasDescriptionFlag = False                                           ' По умолчанию пометки нет

            Dim c                                                                ' Счётчик по колонкам
            For c = 0 To UBound(cols)                                            ' Перебираем все столбцы
                If LCase(Trim(CStr(cols(c)))) = "description" Then               ' Если встретили слово description без регистра
                    hasDescriptionFlag = True                                    ' Отмечаем наличие пометки
                End If                                                            ' Конец проверки колонки
            Next                                                                  ' Следующая колонка

            Dim normalizedCodeKey                                               ' Код в нижнем регистре для дополнительных проверок
            normalizedCodeKey = LCase(Trim(CStr(codeKey)))                      ' Нормализуем код

            If normalizedCodeKey = "мат" And Trim(CStr(codeKey)) <> "" Then    ' Если нашли строку для материалов
                gMaterialCode = Trim(CStr(codeKey))                              ' Сохраняем код материала как в файле
            End If                                                               ' Конец проверки кода материала

            If codeKey <> "" And hasDescriptionFlag = True Then                 ' Если код заполнен и есть пометка description
                gCodesDescriptionKeys = ArrayAppendValue(gCodesDescriptionKeys, codeKey) ' Добавляем код в список поиска по Description
            End If                                                                ' Конец добавления кода

        End If                                                                    ' Конец проверки пустой строки

    Next                                                                          ' Переходим к следующей строке

    LoadCodesFromFile = True                                                      ' Сообщаем об успешной загрузке Code.tsv

End Function                                                                       ' Конец LoadCodesFromFile


' -----------------------------                                                    ' Раздел комментария
' Загрузка библиотек материалов из TSV-файлов                                      ' Описание
' -----------------------------                                                    ' Раздел комментария
Function LoadMaterialLibraries(workFolder)

    Dim metalsPath                                                                ' Полный путь к metals_ru_library.tsv
    metalsPath = workFolder & "\metals_ru_library.tsv"                              ' Файл с марками металлов лежит рядом со скриптом

    Dim compositesPath                                                            ' Полный путь к composites_detect_keywords.tsv
    compositesPath = workFolder & "\composites_detect_keywords.tsv"                ' Файл с ключами композитов лежит рядом со скриптом

    If FileExists(metalsPath) = False Then                                        ' Проверяем наличие файла с металлами
        MsgBox "Не найден metals_ru_library.tsv в папке:" & vbCrLf & workFolder & vbCrLf & _
               "Положи metals_ru_library.tsv рядом со скриптами.", vbExclamation, "BOM Extract" ' Сообщаем об отсутствующем файле
        LoadMaterialLibraries = False                                             ' Сообщаем об ошибке загрузки
        Exit Function                                                             ' Выходим из функции
    End If                                                                        ' Конец проверки наличия metals_ru_library.tsv

    If FileExists(compositesPath) = False Then                                    ' Проверяем наличие файла с ключами композитов
        MsgBox "Не найден composites_detect_keywords.tsv в папке:" & vbCrLf & workFolder & vbCrLf & _
               "Положи composites_detect_keywords.tsv рядом со скриптами.", vbExclamation, "BOM Extract" ' Сообщаем об отсутствии файла
        LoadMaterialLibraries = False                                             ' Сообщаем об ошибке загрузки
        Exit Function                                                             ' Выходим из функции
    End If                                                                        ' Конец проверки наличия composites_detect_keywords.tsv

    gMetalsKeywords = Array()                                                     ' Очищаем массив ключей металлов перед загрузкой
    gCompositeKeywords = Array()                                                  ' Очищаем массив ключевых слов композитов

    Dim readOkMetals                                                             ' Флаг успешного чтения файла металлов
    readOkMetals = False                                                         ' Инициализируем ложью

    Dim metalsContent                                                            ' Содержимое metals_ru_library.tsv
    metalsContent = ReadAllText(metalsPath, readOkMetals)                        ' Читаем файл с марками металлов

    If readOkMetals = False Then                                                 ' Если прочитать металлы не удалось
        MsgBox "Не удалось прочитать metals_ru_library.tsv:" & vbCrLf & metalsPath, vbExclamation, "BOM Extract" ' Показываем ошибку
        LoadMaterialLibraries = False                                             ' Возвращаем ошибку загрузки
        Exit Function                                                             ' Выходим
    End If                                                                        ' Конец проверки чтения metals_ru_library.tsv

    Dim normalizedMetalsText                                                     ' Текст металлов с унифицированными переводами строк
    normalizedMetalsText = Replace(metalsContent, vbCrLf, vbLf)                  ' Заменяем CRLF на LF
    normalizedMetalsText = Replace(normalizedMetalsText, vbCr, vbLf)             ' Убираем одиночные CR

    Dim metalRows                                                                ' Строки файла металлов
    metalRows = Split(normalizedMetalsText, vbLf)                                ' Разбиваем файл на строки

    Dim mi                                                                       ' Счётчик строк по металлам
    For mi = 0 To UBound(metalRows)                                              ' Перебираем все строки таблицы металлов

        Dim metalLine                                                            ' Текущая строка металлов
        metalLine = Trim(CStr(metalRows(mi)))                                    ' Обрезаем пробелы вокруг

        If metalLine = "" Then                                                  ' Пропускаем пустые строки
            ' Пропуск                                                             ' Пояснение
        Else                                                                      ' Есть содержимое строки

            Dim metalCols                                                        ' Колонки строки металлов
            metalCols = Split(metalLine, vbTab)                                  ' Делим строку по табам

            Dim metalMark                                                        ' Марка/ключ металла из второй колонки
            metalMark = ""                                                      ' Инициализируем пустой строкой
            If UBound(metalCols) >= 1 Then                                       ' Проверяем наличие второй колонки
                metalMark = LCase(Trim(CStr(metalCols(1))))                      ' Берём вторую колонку и нормализуем
            End If                                                               ' Конец проверки наличия колонки

            If metalMark <> "" And metalMark <> "марка" Then                  ' Игнорируем пустые и заголовок
                gMetalsKeywords = ArrayAppendValue(gMetalsKeywords, metalMark)   ' Добавляем марку в массив ключей металлов
            End If                                                               ' Конец проверки валидности строки

        End If                                                                  ' Конец проверки пустой строки

    Next                                                                        ' Следующая строка металлов

    Dim readOkComposite                                                         ' Флаг успешного чтения файла композитов
    readOkComposite = False                                                     ' Инициализируем ложью

    Dim compositesContent                                                       ' Содержимое composites_detect_keywords.tsv
    compositesContent = ReadAllText(compositesPath, readOkComposite)            ' Читаем файл с ключами композитов

    If readOkComposite = False Then                                             ' Если прочитать файл не удалось
        MsgBox "Не удалось прочитать composites_detect_keywords.tsv:" & vbCrLf & compositesPath, vbExclamation, "BOM Extract" ' Показываем ошибку
        LoadMaterialLibraries = False                                             ' Возвращаем ошибку загрузки
        Exit Function                                                             ' Выходим
    End If                                                                        ' Конец проверки чтения composites_detect_keywords.tsv

    Dim normalizedCompositeText                                                 ' Текст композитов с унифицированными переводами строк
    normalizedCompositeText = Replace(compositesContent, vbCrLf, vbLf)          ' Заменяем CRLF на LF
    normalizedCompositeText = Replace(normalizedCompositeText, vbCr, vbLf)      ' Убираем одиночные CR

    Dim compositeRows                                                           ' Строки файла композитов
    compositeRows = Split(normalizedCompositeText, vbLf)                        ' Делим файл на строки

    Dim ci                                                                       ' Счётчик строк по композитам
    For ci = 0 To UBound(compositeRows)                                          ' Перебираем все строки ключей композитов

        Dim compositeLine                                                       ' Текущая строка ключей
        compositeLine = Trim(CStr(compositeRows(ci)))                           ' Обрезаем пробелы вокруг

        If compositeLine = "" Then                                             ' Пропускаем пустые строки
            ' Пропуск                                                             ' Пояснение
        Else                                                                     ' Есть содержимое строки

            Dim compositeCols                                                   ' Колонки строки композитов
            compositeCols = Split(compositeLine, vbTab)                         ' Делим строку по табуляции

            Dim groupText                                                       ' Имя группы (например, Армирование)
            groupText = ""                                                      ' Инициализация
            If UBound(compositeCols) >= 0 Then                                   ' Если есть первая колонка
                groupText = LCase(Trim(CStr(compositeCols(0))))                 ' Берём группу и нормализуем
            End If                                                               ' Конец проверки наличия группы

            Dim tagText                                                         ' Ключевое слово/тег
            tagText = ""                                                        ' Инициализация
            If UBound(compositeCols) >= 1 Then                                   ' Если есть вторая колонка
                tagText = LCase(CStr(compositeCols(1)))                         ' Берём тег и переводим в нижний регистр без удаления пробелов внутри
            End If                                                               ' Конец проверки наличия тега

            If groupText <> "" And tagText <> "" And groupText <> "группа" And tagText <> "тег" Then ' Проверяем валидность строки и пропускаем заголовок
                Dim entry                                                        ' Запись с данными ключевого слова
                entry = Array(tagText, groupText)                               ' Укладываем тег и группу в массив
                gCompositeKeywords = ArrayAppendValue(gCompositeKeywords, entry) ' Добавляем запись в общий массив ключей
            End If                                                               ' Конец проверки валидности строки композитов

        End If                                                                  ' Конец проверки пустой строки

    Next                                                                        ' Следующая строка композитов

    LoadMaterialLibraries = True                                                 ' Сообщаем об успешной загрузке библиотек

End Function                                                                       ' Конец LoadMaterialLibraries



Function ReadAllText(path, ByRef isOk)

    On Error Resume Next                                                           ' Перехватываем возможные ошибки

    isOk = False                                                                   ' По умолчанию чтение неуспешно

    Dim fso                                                                        ' FileSystemObject
    Set fso = CreateObject("Scripting.FileSystemObject")                           ' Создаём FSO

    Dim f                                                                          ' Текстовый файл
    Set f = fso.OpenTextFile(path, 1, False)                                       ' Открываем на чтение (без автосоздания)

    If Err.Number <> 0 Then                                                        ' Если открыть файл не удалось
        Err.Clear                                                                  ' Чистим ошибку
        ReadAllText = ""                                                          ' Возвращаем пустую строку
        Exit Function                                                              ' Выходим
    End If                                                                         ' Конец проверки открытия

    Dim t                                                                          ' Содержимое файла
    t = f.ReadAll                                                                  ' Читаем весь текст
    f.Close                                                                        ' Закрываем файл

    isOk = True                                                                    ' Отмечаем, что чтение прошло успешно
    ReadAllText = CStr(t)                                                          ' Возвращаем текст как строку

    On Error GoTo 0                                                                ' Снимаем перехват

End Function                                                                        ' Конец ReadAllText


Function ParseFlexibleBoolean(rawValue)

    Dim t                                                                          ' Рабочая строка со значением
    t = LCase(Trim(CStr(rawValue)))                                                ' Нормализуем регистр и пробелы

    t = Replace(t, Chr(34), " ")                                                  ' Убираем двойные кавычки
    t = Replace(t, "'", " ")                                                     ' Убираем одинарные кавычки
    t = Replace(t, vbTab, " ")                                                    ' Заменяем табы на пробелы
    t = Replace(t, vbCr, " ")                                                     ' Убираем CR
    t = Replace(t, vbLf, " ")                                                     ' Убираем LF

    If InStr(t, " ") > 0 Then                                                     ' Если есть пробелы внутри
        t = Split(t, " ")(0)                                                      ' Берём первое слово (до комментариев)
    End If                                                                         ' Конец обработки пробелов

    ParseFlexibleBoolean = (t = "true" Or t = "1" Or t = "yes" Or t = "y" Or t = "да") ' Преобразуем в булево

End Function                                                                        ' Конец ParseFlexibleBoolean


Function ParseProjectCodeList(rawValue)

    Dim prepared                                                                   ' Текст, подготовленный к разбору
    prepared = CStr(rawValue)                                                      ' Приводим к строке
    prepared = Replace(prepared, Chr(34), " ")                                    ' Убираем двойные кавычки
    prepared = Replace(prepared, "'", " ")                                       ' Убираем одинарные кавычки
    prepared = Replace(prepared, vbCr, " ")                                       ' Убираем CR
    prepared = Replace(prepared, vbLf, " ")                                       ' Убираем LF
    prepared = Replace(prepared, vbTab, " ")                                      ' Заменяем табуляции
    prepared = Replace(prepared, ";", " ")                                       ' Заменяем точки с запятой на пробелы
    prepared = Replace(prepared, ",", " ")                                       ' Заменяем запятые на пробелы
    prepared = Replace(prepared, "|", " ")                                       ' Заменяем вертикальные черты
    prepared = Replace(prepared, "/", " ")                                       ' Заменяем косые черты

    prepared = LCase(prepared)                                                     ' Переводим в нижний регистр
    prepared = Replace(prepared, " or ", " ")                                    ' Поддержка разделителя OR
    prepared = Replace(prepared, "или", " ")                                     ' Поддержка русскоязычного "или"
    prepared = Replace(prepared, "and", " ")                                     ' Убираем слово AND, если вдруг встретится

    Dim parts                                                                      ' Части строки после split
    parts = Split(prepared, " ")                                                  ' Делим по пробелам

    Dim arr                                                                        ' Результирующий массив префиксов
    arr = Array()                                                                  ' Начинаем с пустого массива

    Dim i                                                                          ' Счётчик частей
    For i = 0 To UBound(parts)                                                     ' Перебираем все элементы
        Dim p                                                                      ' Текущий фрагмент
        p = Trim(CStr(parts(i)))                                                   ' Чистим пробелы
        If p <> "" Then                                                           ' Игнорируем пустые элементы
            arr = ArrayAppendValue(arr, p)                                         ' Добавляем префикс в массив
        End If                                                                     ' Конец проверки пустоты
    Next                                                                           ' Следующий элемент

    ParseProjectCodeList = arr                                                     ' Возвращаем массив префиксов

End Function                                                                        ' Конец ParseProjectCodeList


' -----------------------------                                                    ' Раздел комментария
' Файлы/папки/строки                                                                 ' Описание
' -----------------------------                                                    ' Раздел комментария
Function WriteAllTextUnicode(path, text)

    On Error Resume Next                                                           ' Перехват ошибок записи
    Dim fso                                                                        ' FileSystemObject
    Set fso = CreateObject("Scripting.FileSystemObject")                           ' Создаём FSO
    Dim f                                                                          ' Файл
    Set f = fso.CreateTextFile(path, True, True)                                   ' True=overwrite, True=Unicode (UTF-16 LE)
    f.Write text                                                                   ' Пишем текст
    f.Close                                                                        ' Закрываем файл
    If Err.Number <> 0 Then                                                        ' Если ошибка
        Err.Clear                                                                  ' Сбрасываем
        WriteAllTextUnicode = False                                                ' Возвращаем False
    Else                                                                           ' Если без ошибок
        WriteAllTextUnicode = True                                                 ' Возвращаем True
    End If                                                                         ' Конец ветвления
    On Error GoTo 0                                                                ' Снимаем перехват

End Function                                                                        ' Конец WriteAllTextUnicode


Function FileExists(path)

    Dim fso                                                                        ' FileSystemObject
    Set fso = CreateObject("Scripting.FileSystemObject")                           ' Создаём FSO
    FileExists = fso.FileExists(path)                                              ' Проверяем существование

End Function                                                                        ' Конец FileExists


Function GetFolderFromFullPath(fullPath)

    Dim fso                                                                        ' FileSystemObject
    Set fso = CreateObject("Scripting.FileSystemObject")                           ' Создаём FSO
    GetFolderFromFullPath = fso.GetParentFolderName(fullPath)                      ' Возвращаем родительскую папку

End Function                                                                        ' Конец GetFolderFromFullPath


Function Quote(s)

    Quote = Chr(34) & s & Chr(34)                                                  ' Оборачиваем строку в кавычки для командной строки

End Function                                                                        ' Конец Quote


Function ParseStartLevel(s)

    Dim t                                                                          ' Рабочая строка
    t = UCase(Trim(CStr(s)))                                                       ' Нормализуем

    If Left(t, 1) = "G" Then                                                       ' Если начинается с G
        t = Mid(t, 2)                                                              ' Отбрасываем G
    End If                                                                         ' Конец обработки G

    If IsNumeric(t) Then                                                           ' Если остался номер
        ParseStartLevel = CLng(t)                                                  ' Возвращаем число
    Else                                                                           ' Иначе
        ParseStartLevel = -1                                                       ' Ошибка парсинга
    End If                                                                         ' Конец ветвления

End Function                                                                        ' Конец ParseStartLevel


' -----------------------------                                                    ' Раздел комментария
' Массивы                                                                            ' Описание
' -----------------------------                                                    ' Раздел комментария
Function ArrayLastIndex(arr)

    On Error Resume Next                                                           ' Перехват (если массив пустой)
    Dim ub                                                                         ' UBound
    ub = UBound(arr)                                                               ' Пытаемся получить верхнюю границу
    If Err.Number <> 0 Then                                                        ' Если ошибка (массив пуст)
        Err.Clear                                                                  ' Сбрасываем
        ArrayLastIndex = -1                                                        ' Возвращаем -1
        Exit Function                                                              ' Выходим
    End If                                                                         ' Конец обработки ошибки
    On Error GoTo 0                                                                ' Снимаем перехват

    If ub < 0 Then                                                                 ' Если вдруг отрицательный
        ArrayLastIndex = -1                                                        ' Возвращаем -1
    Else                                                                           ' Иначе
        ArrayLastIndex = ub                                                        ' Возвращаем индекс
    End If                                                                         ' Конец ветвления

End Function                                                                        ' Конец ArrayLastIndex


Function ArrayAppendValue(arr, value)

    Dim ub                                                                         ' Индекс последнего элемента
    ub = ArrayLastIndex(arr)                                                       ' Получаем индекс

    If ub = -1 Then                                                                ' Если массив пустой
        ReDim arr(0)                                                               ' Создаём 1 элемент
        arr(0) = value                                                             ' Записываем value
    Else                                                                           ' Если массив не пустой
        ReDim Preserve arr(ub + 1)                                                 ' Увеличиваем на 1
        arr(ub + 1) = value                                                        ' Записываем value
    End If                                                                         ' Конец ветвления

    ArrayAppendValue = arr                                                         ' Возвращаем обновлённый массив

End Function                                                                        ' Конец ArrayAppendValue
